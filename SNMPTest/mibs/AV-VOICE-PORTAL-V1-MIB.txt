-- Copyright 2005-2007 by Avaya Inc. All rights reserved.

AV-VOICE-PORTAL-MIB DEFINITIONS ::= BEGIN

IMPORTS
	enterprises
		FROM SNMPv2-SMI
	ituAlarmPerceivedSeverity
		FROM ITU-ALARM-MIB
	OBJECT-TYPE
		FROM RFC-1212
	TRAP-TYPE
		FROM RFC-1215;


avaya OBJECT IDENTIFIER 	::= { enterprises 6889 }

products OBJECT IDENTIFIER 	::= { avaya 1 }

mibs OBJECT IDENTIFIER 	::= { avaya 2 }

avpVoicePortalProd OBJECT IDENTIFIER 	::= { products 17 }

avpVoicePortalMibs OBJECT IDENTIFIER 	::= { mibs 17 }

--
-- Top level components of this MIB
--

avpNotification OBJECT IDENTIFIER 	::= { avpVoicePortalMibs 1 }

avpObjects OBJECT IDENTIFIER 	::= { avpVoicePortalMibs 2 }

avpTraps OBJECT IDENTIFIER 	::= { avpNotification 0 }

--
-- Objects defined and used by Voice Portal MIB
--

avpAlarmTime OBJECT-TYPE
	SYNTAX  OCTET STRING
	ACCESS read-only
	STATUS mandatory
	DESCRIPTION
		"Date and Time that the alarm occurred"
	::= { avpObjects 1 }


avpAlarmLoc OBJECT-TYPE
	SYNTAX  OCTET STRING
	ACCESS read-only
	STATUS mandatory
	DESCRIPTION
		"Location (system name/IP) where alarm occurred"
	::= { avpObjects 2 }


avpAlarmSev OBJECT-TYPE
	SYNTAX  OCTET STRING
	ACCESS read-only
	STATUS mandatory
	DESCRIPTION
		"Sevrity of Alarm"
	::= { avpObjects 3 }


avpAlarmText OBJECT-TYPE
	SYNTAX  OCTET STRING
	ACCESS read-only
	STATUS mandatory
	DESCRIPTION
		"Text description associated with this alarm"
	::= { avpObjects 4 }


avpVoicePortalExtendedMIB OBJECT IDENTIFIER 	::= { avpVoicePortalMibs 3 }

avpMPPTable OBJECT-TYPE
	SYNTAX  SEQUENCE OF AvpMPPEntry
	ACCESS not-accessible
	STATUS mandatory
	DESCRIPTION
		""
	::= { avpVoicePortalExtendedMIB 1 }


avpMPPEntry OBJECT-TYPE
	SYNTAX  AvpMPPEntry
	ACCESS not-accessible
	STATUS mandatory
	DESCRIPTION
		"Provides basic status and some configuration information for a single MPP."
	INDEX {
 		IMPLIED avpMPPEntryName }
	::= { avpMPPTable 1 }


AvpMPPEntry ::= SEQUENCE {

	avpMPPEntryName                   OCTET STRING,
	avpMPPEntryIPAddress              OCTET STRING,
	avpMPPEntryVersion                OCTET STRING,
	avpMPPEntryRequestedState         OCTET STRING,
	avpMPPEntryConfiguredState        OCTET STRING,
	avpMPPEntryCurrentState           OCTET STRING,
	avpMPPEntryCPUUsagePercent        OCTET STRING,
	avpMPPEntryDiskUsagePercent       OCTET STRING,
	avpMPPEntryMemoryUsagePercent     OCTET STRING,
	avpMPPEntryCPUUsage24HrAverage    OCTET STRING,
	avpMPPEntryDiskUsage24HrAverage   OCTET STRING,
	avpMPPEntryMemoryUsage24HrAverage OCTET STRING,
	avpMPPEntryUnacknowledgedAlarms   OCTET STRING,
	avpMPPEntryAcknowledgedAlarms     OCTET STRING,
	avpMPPEntryActiveCalls            OCTET STRING,
	avpMPPEntryCallsToday             OCTET STRING }


avpMPPEntryName OBJECT-TYPE
	SYNTAX  OCTET STRING
	ACCESS read-only
	STATUS mandatory
	DESCRIPTION
		"MPP Name"
	::= { avpMPPEntry 0 }


avpMPPEntryIPAddress OBJECT-TYPE
	SYNTAX  OCTET STRING
	ACCESS read-only
	STATUS mandatory
	DESCRIPTION
		"IP Address of MPP"
	::= { avpMPPEntry 1 }


avpMPPEntryVersion OBJECT-TYPE
	SYNTAX  OCTET STRING
	ACCESS read-only
	STATUS mandatory
	DESCRIPTION
		"Version of software running on MPP"
	::= { avpMPPEntry 2 }


avpMPPEntryRequestedState OBJECT-TYPE
	SYNTAX  OCTET STRING
	ACCESS read-only
	STATUS mandatory
	DESCRIPTION
		"The state that the MPP was requested to be in."
	::= { avpMPPEntry 3 }


avpMPPEntryConfiguredState OBJECT-TYPE
	SYNTAX  OCTET STRING
	ACCESS read-only
	STATUS mandatory
	DESCRIPTION
		"The state that the MPP is configured to be in."
	::= { avpMPPEntry 4 }


avpMPPEntryCurrentState OBJECT-TYPE
	SYNTAX  OCTET STRING
	ACCESS read-only
	STATUS mandatory
	DESCRIPTION
		"The state that the MPP is currently in."
	::= { avpMPPEntry 5 }


avpMPPEntryCPUUsagePercent OBJECT-TYPE
	SYNTAX  OCTET STRING
	ACCESS read-only
	STATUS mandatory
	DESCRIPTION
		"CPU Usage of the MPP (in percent) "
	::= { avpMPPEntry 6 }


avpMPPEntryDiskUsagePercent OBJECT-TYPE
	SYNTAX  OCTET STRING
	ACCESS read-only
	STATUS mandatory
	DESCRIPTION
		"The disk usage of the MPP (in percent) "
	::= { avpMPPEntry 7 }


avpMPPEntryMemoryUsagePercent OBJECT-TYPE
	SYNTAX  OCTET STRING
	ACCESS read-only
	STATUS mandatory
	DESCRIPTION
		"The memory usage of the MPP (in percent) "
	::= { avpMPPEntry 8 }


avpMPPEntryCPUUsage24HrAverage OBJECT-TYPE
	SYNTAX  OCTET STRING
	ACCESS read-only
	STATUS mandatory
	DESCRIPTION
		"The CPU usage of the MPP (in percent) averaged over the last 24 hours"
	::= { avpMPPEntry 9 }


avpMPPEntryDiskUsage24HrAverage OBJECT-TYPE
	SYNTAX  OCTET STRING
	ACCESS read-only
	STATUS mandatory
	DESCRIPTION
		"The disk usage of the MPP (in percent) averaged over the last 24 hours"
	::= { avpMPPEntry 10 }


avpMPPEntryMemoryUsage24HrAverage OBJECT-TYPE
	SYNTAX  OCTET STRING
	ACCESS read-only
	STATUS mandatory
	DESCRIPTION
		"The memory usage of the MPP (in percent) averaged over the last 24 hours"
	::= { avpMPPEntry 11 }


avpMPPEntryUnacknowledgedAlarms OBJECT-TYPE
	SYNTAX  OCTET STRING
	ACCESS read-only
	STATUS mandatory
	DESCRIPTION
		"The number of unacknowledged alarms for the MPP"
	::= { avpMPPEntry 12 }


avpMPPEntryAcknowledgedAlarms OBJECT-TYPE
	SYNTAX  OCTET STRING
	ACCESS read-only
	STATUS mandatory
	DESCRIPTION
		"The number of acknowledged alarms for the MPP"
	::= { avpMPPEntry 13 }


avpMPPEntryActiveCalls OBJECT-TYPE
	SYNTAX  OCTET STRING
	ACCESS read-only
	STATUS mandatory
	DESCRIPTION
		"The number of active calls for the MPP"
	::= { avpMPPEntry 14 }


avpMPPEntryCallsToday OBJECT-TYPE
	SYNTAX  OCTET STRING
	ACCESS read-only
	STATUS mandatory
	DESCRIPTION
		"The number of calls today for the MPP"
	::= { avpMPPEntry 15 }


avpVPMSProperties OBJECT IDENTIFIER 	::= { avpVoicePortalExtendedMIB 2 }

avpVPMSHostname OBJECT-TYPE
	SYNTAX  OCTET STRING
	ACCESS read-only
	STATUS mandatory
	DESCRIPTION
		"The hostname of the VPMS system"
	::= { avpVPMSProperties 0 }


avpVPMSConfiguredMPPCount OBJECT-TYPE
	SYNTAX  OCTET STRING
	ACCESS read-only
	STATUS mandatory
	DESCRIPTION
		"The number of MPP's configured on this VPMS"
	::= { avpVPMSProperties 1 }


avpVPMSUnacknowledgedAlarms OBJECT-TYPE
	SYNTAX  OCTET STRING
	ACCESS read-only
	STATUS mandatory
	DESCRIPTION
		"The number of unacknowledged alarms for the VPMS"
	::= { avpVPMSProperties 2 }


avpVPMSAcknowledgedAlarms OBJECT-TYPE
	SYNTAX  OCTET STRING
	ACCESS read-only
	STATUS mandatory
	DESCRIPTION
		"The number of acknowledged alarms for the VPMS"
	::= { avpVPMSProperties 3 }


avpVPMSSWVersion OBJECT-TYPE
	SYNTAX  OCTET STRING
	ACCESS read-only
	STATUS mandatory
	DESCRIPTION
		"The software version of the VPMS"
	::= { avpVPMSProperties 4 }


avpVPMSName OBJECT-TYPE
	SYNTAX  OCTET STRING
	ACCESS read-only
	STATUS mandatory
	DESCRIPTION
		"The name assigned to the VPMS in the Voice Portal configuration."
	::= { avpVPMSProperties 5 }


avpTableApplications OBJECT-TYPE
	SYNTAX  SEQUENCE OF AvpEntryApplication
	ACCESS not-accessible
	STATUS mandatory
	DESCRIPTION
		"A Tablle of applications configured for this Voice Portal system."
	::= { avpVoicePortalExtendedMIB 3 }


avpEntryApplication OBJECT-TYPE
	SYNTAX  AvpEntryApplication
	ACCESS not-accessible
	STATUS mandatory
	DESCRIPTION
		""
	INDEX {
		avpEntryAppName }
	::= { avpTableApplications 1 }


AvpEntryApplication ::= SEQUENCE {

	avpEntryAppName OCTET STRING,
	avpEntryAppDNIS OCTET STRING,
	avpEntryAppURL  OCTET STRING,
	avpEntryAppCalledURI  OCTET STRING,
	avpEntryAppURL1 OCTET STRING,
	avpEntryAppAssociateURL OCTET STRING,
	avpEntryAppAssociateURL1 OCTET STRING
	}


avpEntryAppName OBJECT-TYPE
	SYNTAX  OCTET STRING
	ACCESS read-only
	STATUS mandatory
	DESCRIPTION
		"The name of the application"
	::= { avpEntryApplication 0 }


avpEntryAppDNIS OBJECT-TYPE
	SYNTAX  OCTET STRING
	ACCESS read-only
	STATUS mandatory
	DESCRIPTION
		"The DNIS or Called Numbers for this application"
	::= { avpEntryApplication 1 }


avpEntryAppURL OBJECT-TYPE
	SYNTAX  OCTET STRING
	ACCESS read-only
	STATUS mandatory
	DESCRIPTION
		"The URL for this application"
	::= { avpEntryApplication 2 }

avpEntryAppCalledURI OBJECT-TYPE
	SYNTAX  OCTET STRING
	ACCESS read-only
	STATUS mandatory
	DESCRIPTION
		"The Called URI Numbers for this application"
	::= { avpEntryApplication 3 }

avpEntryAppURL1 OBJECT-TYPE
	SYNTAX  OCTET STRING
	ACCESS read-only
	STATUS mandatory
	DESCRIPTION
		"The URL1 for this application"
	::= { avpEntryApplication 4 }

avpEntryAppAssociateURL OBJECT-TYPE
	SYNTAX  OCTET STRING
	ACCESS read-only
	STATUS mandatory
	DESCRIPTION
		"The AssociateURL for this application"
	::= { avpEntryApplication 5 }
	
avpEntryAppAssociateURL1 OBJECT-TYPE
	SYNTAX  OCTET STRING
	ACCESS read-only
	STATUS mandatory
	DESCRIPTION
		"The AssociateURL1 for this application"
	::= { avpEntryApplication 6 }

	
avpTableAuxVPMS OBJECT-TYPE
	SYNTAX SEQUENCE OF AvpAuxVPMS
	ACCESS not-accessible
	STATUS mandatory
	DESCRIPTION
		"Display information for each auxiliary VPMS that is configured for this Voice Portal system."
	::= { avpVoicePortalExtendedMIB 4}
avpAuxVPMS OBJECT-TYPE
	SYNTAX AvpAuxVPMS
	ACCESS not-accessible
	STATUS mandatory
	DESCRIPTION
		""
	INDEX { 
		avpAuxVPMSName }
	::= { avpTableAuxVPMS 1 }


AvpAuxVPMS ::= SEQUENCE {
	avpAuxVPMSName OCTET STRING,
	avpAuxVPMSHostAddress OCTET STRING,
	avpAuxVPMSSWVersion OCTET STRING
	}


avpAuxVPMSName OBJECT-TYPE
	SYNTAX  OCTET STRING
	ACCESS read-only
	STATUS mandatory
	DESCRIPTION
		"The name assigned to the auxiliary vpms in the Voice Portal Configuration."
	::= { avpAuxVPMS 0 }
	
avpAuxVPMSHostAddress OBJECT-TYPE
	SYNTAX  OCTET STRING
	ACCESS read-only
	STATUS mandatory
	DESCRIPTION
		"The hostname or IP address of the auxiliary vpms"
	::= { avpAuxVPMS 1 }


avpAuxVPMSSWVersion OBJECT-TYPE
	SYNTAX  OCTET STRING
	ACCESS read-only
	STATUS mandatory
	DESCRIPTION
		"The software version of the auxiliary VPMS"
	::= { avpAuxVPMS 2 }


avpVoicePortal OBJECT IDENTIFIER 	::= { avpVoicePortalMibs 4 }


--
-- Notification Types
--

avpUnknown TRAP-TYPE
	ENTERPRISE avpNotification
	VARIABLES {
		avpAlarmTime,
		avpAlarmLoc,
		avpAlarmSev,
		avpAlarmText}
	DESCRIPTION 
		"An unknown alarm condition"
 ::= 993


avpTRAPQLICE00001 TRAP-TYPE
	ENTERPRISE avpNotification
	VARIABLES {
		avpAlarmTime,
		avpAlarmLoc,
		avpAlarmSev,
		avpAlarmText}
	DESCRIPTION 
		"Unable to contact WebLM server"
 ::= 1


avpTRAPQLICE00002 TRAP-TYPE
	ENTERPRISE avpNotification
	VARIABLES {
		avpAlarmTime,
		avpAlarmLoc,
		avpAlarmSev,
		avpAlarmText}
	DESCRIPTION 
		"License grace period has exceeded"
 ::= 2


avpTRAPQLICE00003 TRAP-TYPE
	ENTERPRISE avpNotification
	VARIABLES {
		avpAlarmTime,
		avpAlarmLoc,
		avpAlarmSev,
		avpAlarmText}
	DESCRIPTION 
		"License has expired"
 ::= 3


avpTRAPQLICE00004 TRAP-TYPE
	ENTERPRISE avpNotification
	VARIABLES {
		avpAlarmTime,
		avpAlarmLoc,
		avpAlarmSev,
		avpAlarmText}
	DESCRIPTION 
		"License information is not available in the database"
 ::= 4


avpTRAPQLICE00005 TRAP-TYPE
	ENTERPRISE avpNotification
	VARIABLES {
		avpAlarmTime,
		avpAlarmLoc,
		avpAlarmSev,
		avpAlarmText}
	DESCRIPTION 
		"An SQL exception has occurred."
 ::= 5


avpTRAPQCXI00001 TRAP-TYPE
	ENTERPRISE avpNotification
	VARIABLES {
		avpAlarmTime,
		avpAlarmLoc,
		avpAlarmSev,
		avpAlarmText}
	DESCRIPTION 
		"IPC connection to SessionManager failed"
 ::= 6


avpTRAPQCXI00002 TRAP-TYPE
	ENTERPRISE avpNotification
	VARIABLES {
		avpAlarmTime,
		avpAlarmLoc,
		avpAlarmSev,
		avpAlarmText}
	DESCRIPTION 
		"Invalid parameter sent to a function"
 ::= 7


avpTRAPQCXI00003 TRAP-TYPE
	ENTERPRISE avpNotification
	VARIABLES {
		avpAlarmTime,
		avpAlarmLoc,
		avpAlarmSev,
		avpAlarmText}
	DESCRIPTION 
		"No IPC connection, function failed"
 ::= 8


avpTRAPQCXI00004 TRAP-TYPE
	ENTERPRISE avpNotification
	VARIABLES {
		avpAlarmTime,
		avpAlarmLoc,
		avpAlarmSev,
		avpAlarmText}
	DESCRIPTION 
		"Caught unknown exception in function"
 ::= 9


avpTRAPQCXI00005 TRAP-TYPE
	ENTERPRISE avpNotification
	VARIABLES {
		avpAlarmTime,
		avpAlarmLoc,
		avpAlarmSev,
		avpAlarmText}
	DESCRIPTION 
		"Out of memory"
 ::= 10


avpTRAPQCXI00006 TRAP-TYPE
	ENTERPRISE avpNotification
	VARIABLES {
		avpAlarmTime,
		avpAlarmLoc,
		avpAlarmSev,
		avpAlarmText}
	DESCRIPTION 
		"Error from CXI engine!"
 ::= 11


avpTRAPQCXI00007 TRAP-TYPE
	ENTERPRISE avpNotification
	VARIABLES {
		avpAlarmTime,
		avpAlarmLoc,
		avpAlarmSev,
		avpAlarmText}
	DESCRIPTION 
		"Error connecting to IPC channel"
 ::= 12


avpTRAPQCXI00008 TRAP-TYPE
	ENTERPRISE avpNotification
	VARIABLES {
		avpAlarmTime,
		avpAlarmLoc,
		avpAlarmSev,
		avpAlarmText}
	DESCRIPTION 
		"Error sending Ready message to SessionManager"
 ::= 13


avpTRAPQCXI00009 TRAP-TYPE
	ENTERPRISE avpNotification
	VARIABLES {
		avpAlarmTime,
		avpAlarmLoc,
		avpAlarmSev,
		avpAlarmText}
	DESCRIPTION 
		"Empty log slot"
 ::= 14


avpTRAPQCXI00010 TRAP-TYPE
	ENTERPRISE avpNotification
	VARIABLES {
		avpAlarmTime,
		avpAlarmLoc,
		avpAlarmSev,
		avpAlarmText}
	DESCRIPTION 
		"Non-existant session"
 ::= 15


avpTRAPQCXI00011 TRAP-TYPE
	ENTERPRISE avpNotification
	VARIABLES {
		avpAlarmTime,
		avpAlarmLoc,
		avpAlarmSev,
		avpAlarmText}
	DESCRIPTION 
		"Failed to route event to a session"
 ::= 16


avpTRAPQCXI00012 TRAP-TYPE
	ENTERPRISE avpNotification
	VARIABLES {
		avpAlarmTime,
		avpAlarmLoc,
		avpAlarmSev,
		avpAlarmText}
	DESCRIPTION 
		"Received invalid message in function"
 ::= 17


avpTRAPQCXI00013 TRAP-TYPE
	ENTERPRISE avpNotification
	VARIABLES {
		avpAlarmTime,
		avpAlarmLoc,
		avpAlarmSev,
		avpAlarmText}
	DESCRIPTION 
		"IPC connection failed.  Max number of attempts reached"
 ::= 18


avpTRAPQCXI00016 TRAP-TYPE
	ENTERPRISE avpNotification
	VARIABLES {
		avpAlarmTime,
		avpAlarmLoc,
		avpAlarmSev,
		avpAlarmText}
	DESCRIPTION 
		"CCXML page error in event with invalid argument"
 ::= 19


avpTRAPQCXI00017 TRAP-TYPE
	ENTERPRISE avpNotification
	VARIABLES {
		avpAlarmTime,
		avpAlarmLoc,
		avpAlarmSev,
		avpAlarmText}
	DESCRIPTION 
		"Handle already exists"
 ::= 20


avpTRAPQADMN10001 TRAP-TYPE
	ENTERPRISE avpNotification
	VARIABLES {
		avpAlarmTime,
		avpAlarmLoc,
		avpAlarmSev,
		avpAlarmText}
	DESCRIPTION 
		"MPP Maintenance caught unknown exception"
 ::= 21


avpTRAPQADMN10002 TRAP-TYPE
	ENTERPRISE avpNotification
	VARIABLES {
		avpAlarmTime,
		avpAlarmLoc,
		avpAlarmSev,
		avpAlarmText}
	DESCRIPTION 
		"MPP Maintenance purge failed because directory does not exist"
 ::= 22


avpTRAPQADMN10003 TRAP-TYPE
	ENTERPRISE avpNotification
	VARIABLES {
		avpAlarmTime,
		avpAlarmLoc,
		avpAlarmSev,
		avpAlarmText}
	DESCRIPTION 
		"MPP Maintenance purge failed cannot convert Retention Days value to integer"
 ::= 23


avpTRAPQADMN10004 TRAP-TYPE
	ENTERPRISE avpNotification
	VARIABLES {
		avpAlarmTime,
		avpAlarmLoc,
		avpAlarmSev,
		avpAlarmText}
	DESCRIPTION 
		"MPP Maintenance purge failed due to bad Retention Days value"
 ::= 24


avpTRAPQADMN10005 TRAP-TYPE
	ENTERPRISE avpNotification
	VARIABLES {
		avpAlarmTime,
		avpAlarmLoc,
		avpAlarmSev,
		avpAlarmText}
	DESCRIPTION 
		"MPP Maintenance purge failed cannot convert year/month/day value to integer"
 ::= 25


avpTRAPQSYSM00001 TRAP-TYPE
	ENTERPRISE avpNotification
	VARIABLES {
		avpAlarmTime,
		avpAlarmLoc,
		avpAlarmSev,
		avpAlarmText}
	DESCRIPTION 
		"MPP System Manager initialization of mgt library failed"
 ::= 26


avpTRAPQSYSM00002 TRAP-TYPE
	ENTERPRISE avpNotification
	VARIABLES {
		avpAlarmTime,
		avpAlarmLoc,
		avpAlarmSev,
		avpAlarmText}
	DESCRIPTION 
		"MPP System Manager initialization failed with error"
 ::= 27


avpTRAPQSYSM00003 TRAP-TYPE
	ENTERPRISE avpNotification
	VARIABLES {
		avpAlarmTime,
		avpAlarmLoc,
		avpAlarmSev,
		avpAlarmText}
	DESCRIPTION 
		"MPP System Manager cannot access config file"
 ::= 28


avpTRAPQSYSM00004 TRAP-TYPE
	ENTERPRISE avpNotification
	VARIABLES {
		avpAlarmTime,
		avpAlarmLoc,
		avpAlarmSev,
		avpAlarmText}
	DESCRIPTION 
		"Cannot create message object"
 ::= 29


avpTRAPQSYSM00005 TRAP-TYPE
	ENTERPRISE avpNotification
	VARIABLES {
		avpAlarmTime,
		avpAlarmLoc,
		avpAlarmSev,
		avpAlarmText}
	DESCRIPTION 
		"Cannot register message callbacks"
 ::= 30


avpTRAPQSYSM00006 TRAP-TYPE
	ENTERPRISE avpNotification
	VARIABLES {
		avpAlarmTime,
		avpAlarmLoc,
		avpAlarmSev,
		avpAlarmText}
	DESCRIPTION 
		"Cannot accept message connection"
 ::= 31


avpTRAPQSYSM00007 TRAP-TYPE
	ENTERPRISE avpNotification
	VARIABLES {
		avpAlarmTime,
		avpAlarmLoc,
		avpAlarmSev,
		avpAlarmText}
	DESCRIPTION 
		"Cannot publish MPP configuration data"
 ::= 32


avpTRAPQSYSM00008 TRAP-TYPE
	ENTERPRISE avpNotification
	VARIABLES {
		avpAlarmTime,
		avpAlarmLoc,
		avpAlarmSev,
		avpAlarmText}
	DESCRIPTION 
		"MPP startup aborted because process failed to start"
 ::= 33


avpTRAPQSYSM00009 TRAP-TYPE
	ENTERPRISE avpNotification
	VARIABLES {
		avpAlarmTime,
		avpAlarmLoc,
		avpAlarmSev,
		avpAlarmText}
	DESCRIPTION 
		"During MPP startup because process failed to start"
 ::= 34


avpTRAPQSYSM00010 TRAP-TYPE
	ENTERPRISE avpNotification
	VARIABLES {
		avpAlarmTime,
		avpAlarmLoc,
		avpAlarmSev,
		avpAlarmText}
	DESCRIPTION 
		"Failed to execute system"
 ::= 35


avpTRAPQSYSM00011 TRAP-TYPE
	ENTERPRISE avpNotification
	VARIABLES {
		avpAlarmTime,
		avpAlarmLoc,
		avpAlarmSev,
		avpAlarmText}
	DESCRIPTION 
		"Unknown command was issued from the MMS"
 ::= 36


avpTRAPQSYSM00013 TRAP-TYPE
	ENTERPRISE avpNotification
	VARIABLES {
		avpAlarmTime,
		avpAlarmLoc,
		avpAlarmSev,
		avpAlarmText}
	DESCRIPTION 
		"Command issued from the MMS was ignored because the MPP requires further configuration"
 ::= 37


avpTRAPQSYSM00014 TRAP-TYPE
	ENTERPRISE avpNotification
	VARIABLES {
		avpAlarmTime,
		avpAlarmLoc,
		avpAlarmSev,
		avpAlarmText}
	DESCRIPTION 
		"Failed to send a message"
 ::= 38


avpTRAPQSYSM00015 TRAP-TYPE
	ENTERPRISE avpNotification
	VARIABLES {
		avpAlarmTime,
		avpAlarmLoc,
		avpAlarmSev,
		avpAlarmText}
	DESCRIPTION 
		"Failed to issue command to process"
 ::= 39


avpTRAPQSYSM00016 TRAP-TYPE
	ENTERPRISE avpNotification
	VARIABLES {
		avpAlarmTime,
		avpAlarmLoc,
		avpAlarmSev,
		avpAlarmText}
	DESCRIPTION 
		"Failed to respond to MMS heartbeat request"
 ::= 40


avpTRAPQSYSM00017 TRAP-TYPE
	ENTERPRISE avpNotification
	VARIABLES {
		avpAlarmTime,
		avpAlarmLoc,
		avpAlarmSev,
		avpAlarmText}
	DESCRIPTION 
		"Failed to create process"
 ::= 41


avpTRAPQSYSM00018 TRAP-TYPE
	ENTERPRISE avpNotification
	VARIABLES {
		avpAlarmTime,
		avpAlarmLoc,
		avpAlarmSev,
		avpAlarmText}
	DESCRIPTION 
		"Failed to send signal to process"
 ::= 42


avpTRAPQSYSM00019 TRAP-TYPE
	ENTERPRISE avpNotification
	VARIABLES {
		avpAlarmTime,
		avpAlarmLoc,
		avpAlarmSev,
		avpAlarmText}
	DESCRIPTION 
		"Unexpected exception occurred"
 ::= 43


avpTRAPQSYSM00020 TRAP-TYPE
	ENTERPRISE avpNotification
	VARIABLES {
		avpAlarmTime,
		avpAlarmLoc,
		avpAlarmSev,
		avpAlarmText}
	DESCRIPTION 
		"MPP Process stopped sending keep-alive messages is being terminated"
 ::= 44


avpTRAPQSYSM00022 TRAP-TYPE
	ENTERPRISE avpNotification
	VARIABLES {
		avpAlarmTime,
		avpAlarmLoc,
		avpAlarmSev,
		avpAlarmText}
	DESCRIPTION 
		"MPP Process stopped unexpectedly. Restart count of exhausted"
 ::= 45


avpTRAPQSYSM00023 TRAP-TYPE
	ENTERPRISE avpNotification
	VARIABLES {
		avpAlarmTime,
		avpAlarmLoc,
		avpAlarmSev,
		avpAlarmText}
	DESCRIPTION 
		"MPP Process initialization failed"
 ::= 46


avpTRAPQSYSM00024 TRAP-TYPE
	ENTERPRISE avpNotification
	VARIABLES {
		avpAlarmTime,
		avpAlarmLoc,
		avpAlarmSev,
		avpAlarmText}
	DESCRIPTION 
		"Memory allocation failure"
 ::= 47


avpTRAPQSYSM00025 TRAP-TYPE
	ENTERPRISE avpNotification
	VARIABLES {
		avpAlarmTime,
		avpAlarmLoc,
		avpAlarmSev,
		avpAlarmText}
	DESCRIPTION 
		"MPP configuration failure because configuration data is empty"
 ::= 48


avpTRAPQSYSM00026 TRAP-TYPE
	ENTERPRISE avpNotification
	VARIABLES {
		avpAlarmTime,
		avpAlarmLoc,
		avpAlarmSev,
		avpAlarmText}
	DESCRIPTION 
		"MPP Cpu use has exceeded configured threshold"
 ::= 49


avpTRAPQSYSM00027 TRAP-TYPE
	ENTERPRISE avpNotification
	VARIABLES {
		avpAlarmTime,
		avpAlarmLoc,
		avpAlarmSev,
		avpAlarmText}
	DESCRIPTION 
		"MPP Memory use has exceeded configured threshold"
 ::= 50


avpTRAPQSYSM00028 TRAP-TYPE
	ENTERPRISE avpNotification
	VARIABLES {
		avpAlarmTime,
		avpAlarmLoc,
		avpAlarmSev,
		avpAlarmText}
	DESCRIPTION 
		"MPP Disk use has exceeded configured threshold"
 ::= 51


avpTRAPQSYSM00029 TRAP-TYPE
	ENTERPRISE avpNotification
	VARIABLES {
		avpAlarmTime,
		avpAlarmLoc,
		avpAlarmSev,
		avpAlarmText}
	DESCRIPTION 
		"The MPP process cannot be stopped in its current state"
 ::= 52


avpTRAPQVB00001 TRAP-TYPE
	ENTERPRISE avpNotification
	VARIABLES {
		avpAlarmTime,
		avpAlarmLoc,
		avpAlarmSev,
		avpAlarmText}
	DESCRIPTION 
		"An unknown exception occurred"
 ::= 53


avpTRAPQVB00002 TRAP-TYPE
	ENTERPRISE avpNotification
	VARIABLES {
		avpAlarmTime,
		avpAlarmLoc,
		avpAlarmSev,
		avpAlarmText}
	DESCRIPTION 
		"Could not establish a connection with SessionManager"
 ::= 54


avpTRAPQVB00003 TRAP-TYPE
	ENTERPRISE avpNotification
	VARIABLES {
		avpAlarmTime,
		avpAlarmLoc,
		avpAlarmSev,
		avpAlarmText}
	DESCRIPTION 
		"Browser execution terminated abnormally"
 ::= 55


avpTRAPQVB00004 TRAP-TYPE
	ENTERPRISE avpNotification
	VARIABLES {
		avpAlarmTime,
		avpAlarmLoc,
		avpAlarmSev,
		avpAlarmText}
	DESCRIPTION 
		"Encountered exception creating new browser instance"
 ::= 56


avpTRAPQVB00005 TRAP-TYPE
	ENTERPRISE avpNotification
	VARIABLES {
		avpAlarmTime,
		avpAlarmLoc,
		avpAlarmSev,
		avpAlarmText}
	DESCRIPTION 
		"Encountered exception creating voice browser factory"
 ::= 57


avpTRAPQSESM00001 TRAP-TYPE
	ENTERPRISE avpNotification
	VARIABLES {
		avpAlarmTime,
		avpAlarmLoc,
		avpAlarmSev,
		avpAlarmText}
	DESCRIPTION 
		"Network error occured on CCXML message channel"
 ::= 58


avpTRAPQSESM00002 TRAP-TYPE
	ENTERPRISE avpNotification
	VARIABLES {
		avpAlarmTime,
		avpAlarmLoc,
		avpAlarmSev,
		avpAlarmText}
	DESCRIPTION 
		"Network error occured on VXML message channel"
 ::= 59


avpTRAPQSESM00003 TRAP-TYPE
	ENTERPRISE avpNotification
	VARIABLES {
		avpAlarmTime,
		avpAlarmLoc,
		avpAlarmSev,
		avpAlarmText}
	DESCRIPTION 
		"Connect to CCXML process message channel failed"
 ::= 60


avpTRAPQSESM00004 TRAP-TYPE
	ENTERPRISE avpNotification
	VARIABLES {
		avpAlarmTime,
		avpAlarmLoc,
		avpAlarmSev,
		avpAlarmText}
	DESCRIPTION 
		"Connect to VXML process message channel failed"
 ::= 61


avpTRAPQSESM00005 TRAP-TYPE
	ENTERPRISE avpNotification
	VARIABLES {
		avpAlarmTime,
		avpAlarmLoc,
		avpAlarmSev,
		avpAlarmText}
	DESCRIPTION 
		"Unable to get CCXML message channel"
 ::= 62


avpTRAPQSESM00006 TRAP-TYPE
	ENTERPRISE avpNotification
	VARIABLES {
		avpAlarmTime,
		avpAlarmLoc,
		avpAlarmSev,
		avpAlarmText}
	DESCRIPTION 
		"Unable to register CCXML message channel"
 ::= 63


avpTRAPQSESM00007 TRAP-TYPE
	ENTERPRISE avpNotification
	VARIABLES {
		avpAlarmTime,
		avpAlarmLoc,
		avpAlarmSev,
		avpAlarmText}
	DESCRIPTION 
		"Unable to get VXML message channel"
 ::= 64


avpTRAPQSESM00008 TRAP-TYPE
	ENTERPRISE avpNotification
	VARIABLES {
		avpAlarmTime,
		avpAlarmLoc,
		avpAlarmSev,
		avpAlarmText}
	DESCRIPTION 
		"Unable to register VXML message channel"
 ::= 65


avpTRAPQSESM00009 TRAP-TYPE
	ENTERPRISE avpNotification
	VARIABLES {
		avpAlarmTime,
		avpAlarmLoc,
		avpAlarmSev,
		avpAlarmText}
	DESCRIPTION 
		"Unable to send message to CCXML channel"
 ::= 66


avpTRAPQSESM00010 TRAP-TYPE
	ENTERPRISE avpNotification
	VARIABLES {
		avpAlarmTime,
		avpAlarmLoc,
		avpAlarmSev,
		avpAlarmText}
	DESCRIPTION 
		"Unable to send message to VXML channel"
 ::= 67


avpTRAPQSESM00011 TRAP-TYPE
	ENTERPRISE avpNotification
	VARIABLES {
		avpAlarmTime,
		avpAlarmLoc,
		avpAlarmSev,
		avpAlarmText}
	DESCRIPTION 
		"ASR connect to server failed to initialized"
 ::= 68


avpTRAPQSESM00012 TRAP-TYPE
	ENTERPRISE avpNotification
	VARIABLES {
		avpAlarmTime,
		avpAlarmLoc,
		avpAlarmSev,
		avpAlarmText}
	DESCRIPTION 
		"ASR provider error"
 ::= 69


avpTRAPQSESM00013 TRAP-TYPE
	ENTERPRISE avpNotification
	VARIABLES {
		avpAlarmTime,
		avpAlarmLoc,
		avpAlarmSev,
		avpAlarmText}
	DESCRIPTION 
		"Timeout waiting for ASR to initialize"
 ::= 70


avpTRAPQSESM00014 TRAP-TYPE
	ENTERPRISE avpNotification
	VARIABLES {
		avpAlarmTime,
		avpAlarmLoc,
		avpAlarmSev,
		avpAlarmText}
	DESCRIPTION 
		"TTS connect to server failed to initialized"
 ::= 71


avpTRAPQSESM00015 TRAP-TYPE
	ENTERPRISE avpNotification
	VARIABLES {
		avpAlarmTime,
		avpAlarmLoc,
		avpAlarmSev,
		avpAlarmText}
	DESCRIPTION 
		"Timeout waiting for TTS to initialize"
 ::= 72


avpTRAPQSESM00016 TRAP-TYPE
	ENTERPRISE avpNotification
	VARIABLES {
		avpAlarmTime,
		avpAlarmLoc,
		avpAlarmSev,
		avpAlarmText}
	DESCRIPTION 
		"Unable to create telephony play record endpoint"
 ::= 73


avpTRAPQSESM00017 TRAP-TYPE
	ENTERPRISE avpNotification
	VARIABLES {
		avpAlarmTime,
		avpAlarmLoc,
		avpAlarmSev,
		avpAlarmText}
	DESCRIPTION 
		"Unable to create telephony speech dialog object"
 ::= 74


avpTRAPQSESM00018 TRAP-TYPE
	ENTERPRISE avpNotification
	VARIABLES {
		avpAlarmTime,
		avpAlarmLoc,
		avpAlarmSev,
		avpAlarmText}
	DESCRIPTION 
		"Could not start ASR session"
 ::= 75


avpTRAPQSESM00019 TRAP-TYPE
	ENTERPRISE avpNotification
	VARIABLES {
		avpAlarmTime,
		avpAlarmLoc,
		avpAlarmSev,
		avpAlarmText}
	DESCRIPTION 
		"Unable to create ASR port object"
 ::= 76


avpTRAPQSESM00020 TRAP-TYPE
	ENTERPRISE avpNotification
	VARIABLES {
		avpAlarmTime,
		avpAlarmLoc,
		avpAlarmSev,
		avpAlarmText}
	DESCRIPTION 
		"Could not start TTS session"
 ::= 77


avpTRAPQSESM00021 TRAP-TYPE
	ENTERPRISE avpNotification
	VARIABLES {
		avpAlarmTime,
		avpAlarmLoc,
		avpAlarmSev,
		avpAlarmText}
	DESCRIPTION 
		"Unable to create TTS port object"
 ::= 78


avpTRAPQSESM00022 TRAP-TYPE
	ENTERPRISE avpNotification
	VARIABLES {
		avpAlarmTime,
		avpAlarmLoc,
		avpAlarmSev,
		avpAlarmText}
	DESCRIPTION 
		"Caught Exception, session is exiting"
 ::= 79


avpTRAPQSESM00023 TRAP-TYPE
	ENTERPRISE avpNotification
	VARIABLES {
		avpAlarmTime,
		avpAlarmLoc,
		avpAlarmSev,
		avpAlarmText}
	DESCRIPTION 
		"Caught Exception in main, exiting SessionManager"
 ::= 80


avpTRAPQSESM00024 TRAP-TYPE
	ENTERPRISE avpNotification
	VARIABLES {
		avpAlarmTime,
		avpAlarmLoc,
		avpAlarmSev,
		avpAlarmText}
	DESCRIPTION 
		"Connection to (CCXML,VXML) process, failed"
 ::= 81


avpTRAPQSESM00025 TRAP-TYPE
	ENTERPRISE avpNotification
	VARIABLES {
		avpAlarmTime,
		avpAlarmLoc,
		avpAlarmSev,
		avpAlarmText}
	DESCRIPTION 
		"Error has occured with connection to process, unable to process calls"
 ::= 82


avpTRAPQSESM00026 TRAP-TYPE
	ENTERPRISE avpNotification
	VARIABLES {
		avpAlarmTime,
		avpAlarmLoc,
		avpAlarmSev,
		avpAlarmText}
	DESCRIPTION 
		"Unable to reconnect to (CCXML,VXML) process, SessionManager is exiting"
 ::= 83


avpTRAPQSESM00027 TRAP-TYPE
	ENTERPRISE avpNotification
	VARIABLES {
		avpAlarmTime,
		avpAlarmLoc,
		avpAlarmSev,
		avpAlarmText}
	DESCRIPTION 
		"Unable to create path"
 ::= 84


avpTRAPQSESM00028 TRAP-TYPE
	ENTERPRISE avpNotification
	VARIABLES {
		avpAlarmTime,
		avpAlarmLoc,
		avpAlarmSev,
		avpAlarmText}
	DESCRIPTION 
		"Error opening file"
 ::= 85


avpTRAPQSESM00029 TRAP-TYPE
	ENTERPRISE avpNotification
	VARIABLES {
		avpAlarmTime,
		avpAlarmLoc,
		avpAlarmSev,
		avpAlarmText}
	DESCRIPTION 
		"Error writing to file"
 ::= 86


avpTRAPQSESM00030 TRAP-TYPE
	ENTERPRISE avpNotification
	VARIABLES {
		avpAlarmTime,
		avpAlarmLoc,
		avpAlarmSev,
		avpAlarmText}
	DESCRIPTION 
		"ASR provider failed to load"
 ::= 87


avpTRAPQSESM00031 TRAP-TYPE
	ENTERPRISE avpNotification
	VARIABLES {
		avpAlarmTime,
		avpAlarmLoc,
		avpAlarmSev,
		avpAlarmText}
	DESCRIPTION 
		"ASR provider 'CreateProvider' returned NULL"
 ::= 88


avpTRAPQSESM00032 TRAP-TYPE
	ENTERPRISE avpNotification
	VARIABLES {
		avpAlarmTime,
		avpAlarmLoc,
		avpAlarmSev,
		avpAlarmText}
	DESCRIPTION 
		"Invalid ASR provider unable to find 'CreateProvider' symbol"
 ::= 89


avpTRAPQSESM00033 TRAP-TYPE
	ENTERPRISE avpNotification
	VARIABLES {
		avpAlarmTime,
		avpAlarmLoc,
		avpAlarmSev,
		avpAlarmText}
	DESCRIPTION 
		"ASR provider failed to initialize"
 ::= 90


avpTRAPQSESM00034 TRAP-TYPE
	ENTERPRISE avpNotification
	VARIABLES {
		avpAlarmTime,
		avpAlarmLoc,
		avpAlarmSev,
		avpAlarmText}
	DESCRIPTION 
		"TTS provider failed to load"
 ::= 91


avpTRAPQSESM00035 TRAP-TYPE
	ENTERPRISE avpNotification
	VARIABLES {
		avpAlarmTime,
		avpAlarmLoc,
		avpAlarmSev,
		avpAlarmText}
	DESCRIPTION 
		"TTS provider error, 'CreateProvider' returned NULL"
 ::= 92


avpTRAPQSESM00036 TRAP-TYPE
	ENTERPRISE avpNotification
	VARIABLES {
		avpAlarmTime,
		avpAlarmLoc,
		avpAlarmSev,
		avpAlarmText}
	DESCRIPTION 
		"Invalid TTS provider, unable to find 'CreateProvider' symbol"
 ::= 93


avpTRAPQSESM00037 TRAP-TYPE
	ENTERPRISE avpNotification
	VARIABLES {
		avpAlarmTime,
		avpAlarmLoc,
		avpAlarmSev,
		avpAlarmText}
	DESCRIPTION 
		"TTS provider failed to initialize"
 ::= 94


avpTRAPQSESM00038 TRAP-TYPE
	ENTERPRISE avpNotification
	VARIABLES {
		avpAlarmTime,
		avpAlarmLoc,
		avpAlarmSev,
		avpAlarmText}
	DESCRIPTION 
		"Telephony provider failed to load"
 ::= 95


avpTRAPQSESM00039 TRAP-TYPE
	ENTERPRISE avpNotification
	VARIABLES {
		avpAlarmTime,
		avpAlarmLoc,
		avpAlarmSev,
		avpAlarmText}
	DESCRIPTION 
		"Telephony provider 'CreateProvider' returned NULL"
 ::= 96


avpTRAPQSESM00040 TRAP-TYPE
	ENTERPRISE avpNotification
	VARIABLES {
		avpAlarmTime,
		avpAlarmLoc,
		avpAlarmSev,
		avpAlarmText}
	DESCRIPTION 
		"Invalid Telephony provider unable to find 'CreateProvider' symbol"
 ::= 97


avpTRAPQSESM00041 TRAP-TYPE
	ENTERPRISE avpNotification
	VARIABLES {
		avpAlarmTime,
		avpAlarmLoc,
		avpAlarmSev,
		avpAlarmText}
	DESCRIPTION 
		"Telephony MakeCall to CalledURI failed"
 ::= 98


avpTRAPQSESM00042 TRAP-TYPE
	ENTERPRISE avpNotification
	VARIABLES {
		avpAlarmTime,
		avpAlarmLoc,
		avpAlarmSev,
		avpAlarmText}
	DESCRIPTION 
		"Playfile with file failed on EndPoint"
 ::= 99


avpTRAPQSESM00043 TRAP-TYPE
	ENTERPRISE avpNotification
	VARIABLES {
		avpAlarmTime,
		avpAlarmLoc,
		avpAlarmSev,
		avpAlarmText}
	DESCRIPTION 
		"Record with file failed on EndPoint"
 ::= 100


avpTRAPQSESM00044 TRAP-TYPE
	ENTERPRISE avpNotification
	VARIABLES {
		avpAlarmTime,
		avpAlarmLoc,
		avpAlarmSev,
		avpAlarmText}
	DESCRIPTION 
		"TTS operation failed"
 ::= 101


avpTRAPQSESM00045 TRAP-TYPE
	ENTERPRISE avpNotification
	VARIABLES {
		avpAlarmTime,
		avpAlarmLoc,
		avpAlarmSev,
		avpAlarmText}
	DESCRIPTION 
		"ASR SetParameter failed"
 ::= 102


avpTRAPQSESM00046 TRAP-TYPE
	ENTERPRISE avpNotification
	VARIABLES {
		avpAlarmTime,
		avpAlarmLoc,
		avpAlarmSev,
		avpAlarmText}
	DESCRIPTION 
		"LoadGrammar for grammar failed"
 ::= 103


avpTRAPQSESM00047 TRAP-TYPE
	ENTERPRISE avpNotification
	VARIABLES {
		avpAlarmTime,
		avpAlarmLoc,
		avpAlarmSev,
		avpAlarmText}
	DESCRIPTION 
		"Activate Grammar failed"
 ::= 104


avpTRAPQSESM00048 TRAP-TYPE
	ENTERPRISE avpNotification
	VARIABLES {
		avpAlarmTime,
		avpAlarmLoc,
		avpAlarmSev,
		avpAlarmText}
	DESCRIPTION 
		"Start Recognition failed"
 ::= 105


avpTRAPQSESM00049 TRAP-TYPE
	ENTERPRISE avpNotification
	VARIABLES {
		avpAlarmTime,
		avpAlarmLoc,
		avpAlarmSev,
		avpAlarmText}
	DESCRIPTION 
		"Start DTMF Collection failed"
 ::= 106


avpTRAPQSESM00051 TRAP-TYPE
	ENTERPRISE avpNotification
	VARIABLES {
		avpAlarmTime,
		avpAlarmLoc,
		avpAlarmSev,
		avpAlarmText}
	DESCRIPTION 
		"Unable to initialize status shared memory segment"
 ::= 107


avpTRAPQSESM00052 TRAP-TYPE
	ENTERPRISE avpNotification
	VARIABLES {
		avpAlarmTime,
		avpAlarmLoc,
		avpAlarmSev,
		avpAlarmText}
	DESCRIPTION 
		"Unable to add station"
 ::= 108


avpTRAPQSESM00053 TRAP-TYPE
	ENTERPRISE avpNotification
	VARIABLES {
		avpAlarmTime,
		avpAlarmLoc,
		avpAlarmSev,
		avpAlarmText}
	DESCRIPTION 
		"Remove station failed"
 ::= 109


avpTRAPQSESM00054 TRAP-TYPE
	ENTERPRISE avpNotification
	VARIABLES {
		avpAlarmTime,
		avpAlarmLoc,
		avpAlarmSev,
		avpAlarmText}
	DESCRIPTION 
		"Trunks not supported at this time"
 ::= 110


avpTRAPQSESM00056 TRAP-TYPE
	ENTERPRISE avpNotification
	VARIABLES {
		avpAlarmTime,
		avpAlarmLoc,
		avpAlarmSev,
		avpAlarmText}
	DESCRIPTION 
		"CreateCall failed"
 ::= 111


avpTRAPQSESM00057 TRAP-TYPE
	ENTERPRISE avpNotification
	VARIABLES {
		avpAlarmTime,
		avpAlarmLoc,
		avpAlarmSev,
		avpAlarmText}
	DESCRIPTION 
		"Invalid SessionHande"
 ::= 112


avpTRAPQSESM00064 TRAP-TYPE
	ENTERPRISE avpNotification
	VARIABLES {
		avpAlarmTime,
		avpAlarmLoc,
		avpAlarmSev,
		avpAlarmText}
	DESCRIPTION 
		"TTS provider error"
 ::= 113


avpTRAPQSESM00065 TRAP-TYPE
	ENTERPRISE avpNotification
	VARIABLES {
		avpAlarmTime,
		avpAlarmLoc,
		avpAlarmSev,
		avpAlarmText}
	DESCRIPTION 
		"Caught Exception during initialization, SessionManager cannot start"
 ::= 114


avpTRAPQSESM00066 TRAP-TYPE
	ENTERPRISE avpNotification
	VARIABLES {
		avpAlarmTime,
		avpAlarmLoc,
		avpAlarmSev,
		avpAlarmText}
	DESCRIPTION 
		"Telephony Subsystem Error: All Stations Out-Of-Service."
 ::= 195


avpTRAPQTELE00001 TRAP-TYPE
	ENTERPRISE avpNotification
	VARIABLES {
		avpAlarmTime,
		avpAlarmLoc,
		avpAlarmSev,
		avpAlarmText}
	DESCRIPTION 
		"Configuration Error"
 ::= 115


avpTRAPQTELE00002 TRAP-TYPE
	ENTERPRISE avpNotification
	VARIABLES {
		avpAlarmTime,
		avpAlarmLoc,
		avpAlarmSev,
		avpAlarmText}
	DESCRIPTION 
		"Network Error"
 ::= 116


avpTRAPQTELE00003 TRAP-TYPE
	ENTERPRISE avpNotification
	VARIABLES {
		avpAlarmTime,
		avpAlarmLoc,
		avpAlarmSev,
		avpAlarmText}
	DESCRIPTION 
		"Remote Endpoint Error"
 ::= 117


avpTRAPQTELE00004 TRAP-TYPE
	ENTERPRISE avpNotification
	VARIABLES {
		avpAlarmTime,
		avpAlarmLoc,
		avpAlarmSev,
		avpAlarmText}
	DESCRIPTION 
		"Media Error"
 ::= 118


avpTRAPQTELE00005 TRAP-TYPE
	ENTERPRISE avpNotification
	VARIABLES {
		avpAlarmTime,
		avpAlarmLoc,
		avpAlarmSev,
		avpAlarmText}
	DESCRIPTION 
		"Signaling Error"
 ::= 119


avpTRAPQTELE00006 TRAP-TYPE
	ENTERPRISE avpNotification
	VARIABLES {
		avpAlarmTime,
		avpAlarmLoc,
		avpAlarmSev,
		avpAlarmText}
	DESCRIPTION 
		"Call Error"
 ::= 120


avpTRAPQTELE00007 TRAP-TYPE
	ENTERPRISE avpNotification
	VARIABLES {
		avpAlarmTime,
		avpAlarmLoc,
		avpAlarmSev,
		avpAlarmText}
	DESCRIPTION 
		"Call Force Cleared"
 ::= 121


avpTRAPQTELE00008 TRAP-TYPE
	ENTERPRISE avpNotification
	VARIABLES {
		avpAlarmTime,
		avpAlarmLoc,
		avpAlarmSev,
		avpAlarmText}
	DESCRIPTION 
		"All Channels Busy"
 ::= 122


avpTRAPQTELE00009 TRAP-TYPE
	ENTERPRISE avpNotification
	VARIABLES {
		avpAlarmTime,
		avpAlarmLoc,
		avpAlarmSev,
		avpAlarmText}
	DESCRIPTION 
		"Exception Caught"
 ::= 196


avpTRAPQTELE00024 TRAP-TYPE
	ENTERPRISE avpNotification
	VARIABLES {
		avpAlarmTime,
		avpAlarmLoc,
		avpAlarmSev,
		avpAlarmText}
	DESCRIPTION 
		"Call Handler Initialization Failed"
 ::= 197


avpTRAPQTELE00031 TRAP-TYPE
	ENTERPRISE avpNotification
	VARIABLES {
		avpAlarmTime,
		avpAlarmLoc,
		avpAlarmSev,
		avpAlarmText}
	DESCRIPTION 
		"Channel Out of Service"
 ::= 200


avpTRAPQMMS00001 TRAP-TYPE
	ENTERPRISE avpNotification
	VARIABLES {
		avpAlarmTime,
		avpAlarmLoc,
		avpAlarmSev,
		avpAlarmText}
	DESCRIPTION 
		"Cannot create message object"
 ::= 123


avpTRAPQMMS00002 TRAP-TYPE
	ENTERPRISE avpNotification
	VARIABLES {
		avpAlarmTime,
		avpAlarmLoc,
		avpAlarmSev,
		avpAlarmText}
	DESCRIPTION 
		"Connection failure"
 ::= 124


avpTRAPQMMS00003 TRAP-TYPE
	ENTERPRISE avpNotification
	VARIABLES {
		avpAlarmTime,
		avpAlarmLoc,
		avpAlarmSev,
		avpAlarmText}
	DESCRIPTION 
		"Failed to send command to MPP System Manager"
 ::= 125


avpTRAPQADMN01005 TRAP-TYPE
	ENTERPRISE avpNotification
	VARIABLES {
		avpAlarmTime,
		avpAlarmLoc,
		avpAlarmSev,
		avpAlarmText}
	DESCRIPTION 
		"Alarm threshold for failed logins exceeded"
 ::= 126


avpTRAPQCDH00001 TRAP-TYPE
	ENTERPRISE avpNotification
	VARIABLES {
		avpAlarmTime,
		avpAlarmLoc,
		avpAlarmSev,
		avpAlarmText}
	DESCRIPTION 
		"Unable to access configuration data (CDH)"
 ::= 127


avpTRAPQCDH00008 TRAP-TYPE
	ENTERPRISE avpNotification
	VARIABLES {
		avpAlarmTime,
		avpAlarmLoc,
		avpAlarmSev,
		avpAlarmText}
	DESCRIPTION 
		"Scheduled event completed with errors"
 ::= 132


avpTRAPQOMS00034 TRAP-TYPE
	ENTERPRISE avpNotification
	VARIABLES {
		avpAlarmTime,
		avpAlarmLoc,
		avpAlarmSev,
		avpAlarmText}
	DESCRIPTION 
		"Bad date format in from database table"
 ::= 133


avpTRAPQOMS00035 TRAP-TYPE
	ENTERPRISE avpNotification
	VARIABLES {
		avpAlarmTime,
		avpAlarmLoc,
		avpAlarmSev,
		avpAlarmText}
	DESCRIPTION 
		"MPP has port that has not been configured by VPMS"
 ::= 134


avpTRAPQOMS00036 TRAP-TYPE
	ENTERPRISE avpNotification
	VARIABLES {
		avpAlarmTime,
		avpAlarmLoc,
		avpAlarmSev,
		avpAlarmText}
	DESCRIPTION 
		"MPP has port that has not been assigned to it by VPMS"
 ::= 135


avpTRAPQOMS00037 TRAP-TYPE
	ENTERPRISE avpNotification
	VARIABLES {
		avpAlarmTime,
		avpAlarmLoc,
		avpAlarmSev,
		avpAlarmText}
	DESCRIPTION 
		"MPP has port that has been assigned to another MPP by VPMS"
 ::= 136


avpTRAPQOMS00039 TRAP-TYPE
	ENTERPRISE avpNotification
	VARIABLES {
		avpAlarmTime,
		avpAlarmLoc,
		avpAlarmSev,
		avpAlarmText}
	DESCRIPTION 
		"Unknown state received from MPP"
 ::= 137


avpTRAPQOMS00040 TRAP-TYPE
	ENTERPRISE avpNotification
	VARIABLES {
		avpAlarmTime,
		avpAlarmLoc,
		avpAlarmSev,
		avpAlarmText}
	DESCRIPTION 
		"Unknown Exception Occurred"
 ::= 138


avpTRAPQOMS00045 TRAP-TYPE
	ENTERPRISE avpNotification
	VARIABLES {
		avpAlarmTime,
		avpAlarmLoc,
		avpAlarmSev,
		avpAlarmText}
	DESCRIPTION 
		"Error opening realtime database causing OMS to terminate"
 ::= 139


avpTRAPQOMS00047 TRAP-TYPE
	ENTERPRISE avpNotification
	VARIABLES {
		avpAlarmTime,
		avpAlarmLoc,
		avpAlarmSev,
		avpAlarmText}
	DESCRIPTION 
		"Unknown error opening realtime database causing OMS to terminate"
 ::= 140


avpTRAPQOMS00049 TRAP-TYPE
	ENTERPRISE avpNotification
	VARIABLES {
		avpAlarmTime,
		avpAlarmLoc,
		avpAlarmSev,
		avpAlarmText}
	DESCRIPTION 
		"System Data Module(SDM) initialization error occured"
 ::= 141


avpTRAPQOMS00050 TRAP-TYPE
	ENTERPRISE avpNotification
	VARIABLES {
		avpAlarmTime,
		avpAlarmLoc,
		avpAlarmSev,
		avpAlarmText}
	DESCRIPTION 
		"Failed getting session for configuration database (SDM)"
 ::= 142


avpTRAPQOMS00051 TRAP-TYPE
	ENTERPRISE avpNotification
	VARIABLES {
		avpAlarmTime,
		avpAlarmLoc,
		avpAlarmSev,
		avpAlarmText}
	DESCRIPTION 
		"Failed getting instance of configuration database (SDM) Mananger"
 ::= 143


avpTRAPQOMS00052 TRAP-TYPE
	ENTERPRISE avpNotification
	VARIABLES {
		avpAlarmTime,
		avpAlarmLoc,
		avpAlarmSev,
		avpAlarmText}
	DESCRIPTION 
		"Failed getting configuration database (SDM) Voice Portal System"
 ::= 144


avpTRAPQOMS00053 TRAP-TYPE
	ENTERPRISE avpNotification
	VARIABLES {
		avpAlarmTime,
		avpAlarmLoc,
		avpAlarmSev,
		avpAlarmText}
	DESCRIPTION 
		"Failed getting configuration database (SDM) Voice Portal System"
 ::= 145


avpTRAPQOMS00054 TRAP-TYPE
	ENTERPRISE avpNotification
	VARIABLES {
		avpAlarmTime,
		avpAlarmLoc,
		avpAlarmSev,
		avpAlarmText}
	DESCRIPTION 
		"Configuration change dates container not defined"
 ::= 146


avpTRAPQOMS00055 TRAP-TYPE
	ENTERPRISE avpNotification
	VARIABLES {
		avpAlarmTime,
		avpAlarmLoc,
		avpAlarmSev,
		avpAlarmText}
	DESCRIPTION 
		"Configuration change dates resource not defined"
 ::= 147


avpTRAPQOMS00056 TRAP-TYPE
	ENTERPRISE avpNotification
	VARIABLES {
		avpAlarmTime,
		avpAlarmLoc,
		avpAlarmSev,
		avpAlarmText}
	DESCRIPTION 
		"Exception occured while retreiving configuration change dates"
 ::= 148


avpTRAPQOMS00057 TRAP-TYPE
	ENTERPRISE avpNotification
	VARIABLES {
		avpAlarmTime,
		avpAlarmLoc,
		avpAlarmSev,
		avpAlarmText}
	DESCRIPTION 
		"Exception occured while retreiving H.323 configuration"
 ::= 149


avpTRAPQOMS00058 TRAP-TYPE
	ENTERPRISE avpNotification
	VARIABLES {
		avpAlarmTime,
		avpAlarmLoc,
		avpAlarmSev,
		avpAlarmText}
	DESCRIPTION 
		"Global Settings container not defined"
 ::= 150


avpTRAPQOMS00059 TRAP-TYPE
	ENTERPRISE avpNotification
	VARIABLES {
		avpAlarmTime,
		avpAlarmLoc,
		avpAlarmSev,
		avpAlarmText}
	DESCRIPTION 
		"Global Settings resource not defined"
 ::= 151


avpTRAPQOMS00060 TRAP-TYPE
	ENTERPRISE avpNotification
	VARIABLES {
		avpAlarmTime,
		avpAlarmLoc,
		avpAlarmSev,
		avpAlarmText}
	DESCRIPTION 
		"Exception occured while retreiving global settings"
 ::= 152


avpTRAPQOMS00061 TRAP-TYPE
	ENTERPRISE avpNotification
	VARIABLES {
		avpAlarmTime,
		avpAlarmLoc,
		avpAlarmSev,
		avpAlarmText}
	DESCRIPTION 
		"Error retrieving VPMS logging host IP address"
 ::= 153


avpTRAPQOMS00062 TRAP-TYPE
	ENTERPRISE avpNotification
	VARIABLES {
		avpAlarmTime,
		avpAlarmLoc,
		avpAlarmSev,
		avpAlarmText}
	DESCRIPTION 
		"TBD"
 ::= 154


avpTRAPQOMS00063 TRAP-TYPE
	ENTERPRISE avpNotification
	VARIABLES {
		avpAlarmTime,
		avpAlarmLoc,
		avpAlarmSev,
		avpAlarmText}
	DESCRIPTION 
		"VoIP resources not found"
 ::= 155


avpTRAPQOMS00064 TRAP-TYPE
	ENTERPRISE avpNotification
	VARIABLES {
		avpAlarmTime,
		avpAlarmLoc,
		avpAlarmSev,
		avpAlarmText}
	DESCRIPTION 
		"Exception occured while retreiving Voice over IP configuration"
 ::= 156


avpTRAPQOMS00065 TRAP-TYPE
	ENTERPRISE avpNotification
	VARIABLES {
		avpAlarmTime,
		avpAlarmLoc,
		avpAlarmSev,
		avpAlarmText}
	DESCRIPTION 
		"Exception occured while retreiving TTS configuration"
 ::= 157


avpTRAPQOMS00066 TRAP-TYPE
	ENTERPRISE avpNotification
	VARIABLES {
		avpAlarmTime,
		avpAlarmLoc,
		avpAlarmSev,
		avpAlarmText}
	DESCRIPTION 
		"Exception occured while retreiving application configuration"
 ::= 158


avpTRAPQOMS00067 TRAP-TYPE
	ENTERPRISE avpNotification
	VARIABLES {
		avpAlarmTime,
		avpAlarmLoc,
		avpAlarmSev,
		avpAlarmText}
	DESCRIPTION 
		"Exception occured while retreiving ASR configuration"
 ::= 159


avpTRAPQOMS00068 TRAP-TYPE
	ENTERPRISE avpNotification
	VARIABLES {
		avpAlarmTime,
		avpAlarmLoc,
		avpAlarmSev,
		avpAlarmText}
	DESCRIPTION 
		"Exception occured while retreiving Media Processing Platform configuration"
 ::= 160


avpTRAPQOMS00077 TRAP-TYPE
	ENTERPRISE avpNotification
	VARIABLES {
		avpAlarmTime,
		avpAlarmLoc,
		avpAlarmSev,
		avpAlarmText}
	DESCRIPTION 
		"Configuration data exception occured"
 ::= 161


avpTRAPQOMS00078 TRAP-TYPE
	ENTERPRISE avpNotification
	VARIABLES {
		avpAlarmTime,
		avpAlarmLoc,
		avpAlarmSev,
		avpAlarmText}
	DESCRIPTION 
		"Realtime data exception occured"
 ::= 162


avpTRAPQOMS00079 TRAP-TYPE
	ENTERPRISE avpNotification
	VARIABLES {
		avpAlarmTime,
		avpAlarmLoc,
		avpAlarmSev,
		avpAlarmText}
	DESCRIPTION 
		"Manager exception occured"
 ::= 163


avpTRAPQOMS00080 TRAP-TYPE
	ENTERPRISE avpNotification
	VARIABLES {
		avpAlarmTime,
		avpAlarmLoc,
		avpAlarmSev,
		avpAlarmText}
	DESCRIPTION 
		"Error comitting performance data to database"
 ::= 164


avpTRAPQOMS00081 TRAP-TYPE
	ENTERPRISE avpNotification
	VARIABLES {
		avpAlarmTime,
		avpAlarmLoc,
		avpAlarmSev,
		avpAlarmText}
	DESCRIPTION 
		"Error deleting performance data from database"
 ::= 165


avpTRAPQOMS00082 TRAP-TYPE
	ENTERPRISE avpNotification
	VARIABLES {
		avpAlarmTime,
		avpAlarmLoc,
		avpAlarmSev,
		avpAlarmText}
	DESCRIPTION 
		"Configuration data exception occured while fetching data for OMS UI"
 ::= 166


avpTRAPQOMS00083 TRAP-TYPE
	ENTERPRISE avpNotification
	VARIABLES {
		avpAlarmTime,
		avpAlarmLoc,
		avpAlarmSev,
		avpAlarmText}
	DESCRIPTION 
		"Realtime data exception occured while fetching data for OMS UI"
 ::= 167


avpTRAPQOMS00084 TRAP-TYPE
	ENTERPRISE avpNotification
	VARIABLES {
		avpAlarmTime,
		avpAlarmLoc,
		avpAlarmSev,
		avpAlarmText}
	DESCRIPTION 
		"Manager exception occured while fetching data for OMS UI"
 ::= 168


avpTRAPQOMS00085 TRAP-TYPE
	ENTERPRISE avpNotification
	VARIABLES {
		avpAlarmTime,
		avpAlarmLoc,
		avpAlarmSev,
		avpAlarmText}
	DESCRIPTION 
		"Unknown exception occured while fetching data for OMS UI"
 ::= 169


avpTRAPQOMS00088 TRAP-TYPE
	ENTERPRISE avpNotification
	VARIABLES {
		avpAlarmTime,
		avpAlarmLoc,
		avpAlarmSev,
		avpAlarmText}
	DESCRIPTION 
		"MPP marked Not Responding because it failed to respond to multiple poll requests"
 ::= 170


avpTRAPQOMS00090 TRAP-TYPE
	ENTERPRISE avpNotification
	VARIABLES {
		avpAlarmTime,
		avpAlarmLoc,
		avpAlarmSev,
		avpAlarmText}
	DESCRIPTION 
		"Manager exception occured while processing MPP schedule"
 ::= 171


avpTRAPQOMS00095 TRAP-TYPE
	ENTERPRISE avpNotification
	VARIABLES {
		avpAlarmTime,
		avpAlarmLoc,
		avpAlarmSev,
		avpAlarmText}
	DESCRIPTION 
		"MPP unexpectedly entered the error state"
 ::= 172


avpTRAPQOMS00096 TRAP-TYPE
	ENTERPRISE avpNotification
	VARIABLES {
		avpAlarmTime,
		avpAlarmLoc,
		avpAlarmSev,
		avpAlarmText}
	DESCRIPTION 
		"MPP unexpectedly entered the degraded state"
 ::= 173


avpTRAPQOMS00097 TRAP-TYPE
	ENTERPRISE avpNotification
	VARIABLES {
		avpAlarmTime,
		avpAlarmLoc,
		avpAlarmSev,
		avpAlarmText}
	DESCRIPTION 
		"MPP unexpectedly is starting"
 ::= 174


avpTRAPQOMS00098 TRAP-TYPE
	ENTERPRISE avpNotification
	VARIABLES {
		avpAlarmTime,
		avpAlarmLoc,
		avpAlarmSev,
		avpAlarmText}
	DESCRIPTION 
		"MPP unexpectedly stopped"
 ::= 175


avpTRAPQOMS00099 TRAP-TYPE
	ENTERPRISE avpNotification
	VARIABLES {
		avpAlarmTime,
		avpAlarmLoc,
		avpAlarmSev,
		avpAlarmText}
	DESCRIPTION 
		"MPP unexpectedly is stopping"
 ::= 176


avpTRAPQOMS00100 TRAP-TYPE
	ENTERPRISE avpNotification
	VARIABLES {
		avpAlarmTime,
		avpAlarmLoc,
		avpAlarmSev,
		avpAlarmText}
	DESCRIPTION 
		"SQL exception occured saving MPP"
 ::= 177


avpTRAPQOMS00122 TRAP-TYPE
	ENTERPRISE avpNotification
	VARIABLES {
		avpAlarmTime,
		avpAlarmLoc,
		avpAlarmSev,
		avpAlarmText}
	DESCRIPTION 
		"Configuring MPP failed with no result"
 ::= 183


avpTRAPQOMS00123 TRAP-TYPE
	ENTERPRISE avpNotification
	VARIABLES {
		avpAlarmTime,
		avpAlarmLoc,
		avpAlarmSev,
		avpAlarmText}
	DESCRIPTION 
		"Configuring MPP failed with error"
 ::= 184


avpTRAPQOMS00124 TRAP-TYPE
	ENTERPRISE avpNotification
	VARIABLES {
		avpAlarmTime,
		avpAlarmLoc,
		avpAlarmSev,
		avpAlarmText}
	DESCRIPTION 
		"Encrypt/Decrypt Invalid Key Exception occurred"
 ::= 185


avpTRAPQOMS00125 TRAP-TYPE
	ENTERPRISE avpNotification
	VARIABLES {
		avpAlarmTime,
		avpAlarmLoc,
		avpAlarmSev,
		avpAlarmText}
	DESCRIPTION 
		"Encrypt/Decrypt No Such Algorithm Exception occurred"
 ::= 186


avpTRAPQOMS00126 TRAP-TYPE
	ENTERPRISE avpNotification
	VARIABLES {
		avpAlarmTime,
		avpAlarmLoc,
		avpAlarmSev,
		avpAlarmText}
	DESCRIPTION 
		"Encrypt/Decrypt No Such Padding Exception occurred"
 ::= 187


avpTRAPQOMS00128 TRAP-TYPE
	ENTERPRISE avpNotification
	VARIABLES {
		avpAlarmTime,
		avpAlarmLoc,
		avpAlarmSev,
		avpAlarmText}
	DESCRIPTION 
		"Start/Restart failure; MPP failed to accept start command after it was stopped"
 ::= 201


avpTRAPQOMS00129 TRAP-TYPE
	ENTERPRISE avpNotification
	VARIABLES {
		avpAlarmTime,
		avpAlarmLoc,
		avpAlarmSev,
		avpAlarmText}
	DESCRIPTION 
		"Delete MPP failure: Stop request to MPP failed (MPP must be manually stopped to complete deletion)"
 ::= 202


avpTRAPQOMS00140 TRAP-TYPE
	ENTERPRISE avpNotification
	VARIABLES {
		avpAlarmTime,
		avpAlarmLoc,
		avpAlarmSev,
		avpAlarmText}
	DESCRIPTION 
		"Too many consecutive database errors occurred updating the real time database, OMS terminating"
 ::= 194


avpTRAPQOMS00160 TRAP-TYPE
	ENTERPRISE avpNotification
	VARIABLES {
		avpAlarmTime,
		avpAlarmLoc,
		avpAlarmSev,
		avpAlarmText}
	DESCRIPTION 
		"Failed to retrieve initial configuration change dates; OMS will terminate!"
 ::= 203


avpTRAPQASR00005 TRAP-TYPE
	ENTERPRISE avpNotification
	VARIABLES {
		avpAlarmTime,
		avpAlarmLoc,
		avpAlarmSev,
		avpAlarmText}
	DESCRIPTION 
		"Failed initializing ASR server"
 ::= 198


avpTRAPQASR00007 TRAP-TYPE
	ENTERPRISE avpNotification
	VARIABLES {
		avpAlarmTime,
		avpAlarmLoc,
		avpAlarmSev,
		avpAlarmText}
	DESCRIPTION 
		"Caught exception"
 ::= 188


avpTRAPQASR00008 TRAP-TYPE
	ENTERPRISE avpNotification
	VARIABLES {
		avpAlarmTime,
		avpAlarmLoc,
		avpAlarmSev,
		avpAlarmText}
	DESCRIPTION 
		"Caught an unknown exception"
 ::= 189


avpTRAPQTTS00005 TRAP-TYPE
	ENTERPRISE avpNotification
	VARIABLES {
		avpAlarmTime,
		avpAlarmLoc,
		avpAlarmSev,
		avpAlarmText}
	DESCRIPTION 
		"Failed initializing TTS server"
 ::= 199


avpTRAPQTTS00007 TRAP-TYPE
	ENTERPRISE avpNotification
	VARIABLES {
		avpAlarmTime,
		avpAlarmLoc,
		avpAlarmSev,
		avpAlarmText}
	DESCRIPTION 
		"Caught exception"
 ::= 193


avpTRAPQTTS00008 TRAP-TYPE
	ENTERPRISE avpNotification
	VARIABLES {
		avpAlarmTime,
		avpAlarmLoc,
		avpAlarmSev,
		avpAlarmText}
	DESCRIPTION 
		"Caught an unknown exception"
 ::= 190


avpTRAPQMRCP00005 TRAP-TYPE
	ENTERPRISE avpNotification
	VARIABLES {
		avpAlarmTime,
		avpAlarmLoc,
		avpAlarmSev,
		avpAlarmText}
	DESCRIPTION 
		"Callback not registered"
 ::= 191


avpTRAPQMRCP00006 TRAP-TYPE
	ENTERPRISE avpNotification
	VARIABLES {
		avpAlarmTime,
		avpAlarmLoc,
		avpAlarmSev,
		avpAlarmText}
	DESCRIPTION 
		"An unknown exception occurred"
 ::= 192


avpTRAPQCXI00015 TRAP-TYPE
	ENTERPRISE avpNotification
	VARIABLES {
		avpAlarmTime,
		avpAlarmLoc,
		avpAlarmSev,
		avpAlarmText}
	DESCRIPTION 
		"Attempt to use IPC after shutdown initiated"
 ::= 178


avpTRAPQSYSM00012 TRAP-TYPE
	ENTERPRISE avpNotification
	VARIABLES {
		avpAlarmTime,
		avpAlarmLoc,
		avpAlarmSev,
		avpAlarmText}
	DESCRIPTION 
		"Command issued from the MMS was ignored because the MPP was in the wrong running state"
 ::= 179


avpTRAPQSYSM00021 TRAP-TYPE
	ENTERPRISE avpNotification
	VARIABLES {
		avpAlarmTime,
		avpAlarmLoc,
		avpAlarmSev,
		avpAlarmText}
	DESCRIPTION 
		"MPP Process stopped unexpectedly. Restarting the process"
 ::= 180


avpTRAPQSESM00050 TRAP-TYPE
	ENTERPRISE avpNotification
	VARIABLES {
		avpAlarmTime,
		avpAlarmLoc,
		avpAlarmSev,
		avpAlarmText}
	DESCRIPTION 
		"No application configured for call with DNIS"
 ::= 181


avpTRAPQOMS00041 TRAP-TYPE
	ENTERPRISE avpNotification
	VARIABLES {
		avpAlarmTime,
		avpAlarmLoc,
		avpAlarmSev,
		avpAlarmText}
	DESCRIPTION 
		"Exception Occurred"
 ::= 182


avpTRAPQOMS00042 TRAP-TYPE
	ENTERPRISE avpNotification
	VARIABLES {
		avpAlarmTime,
		avpAlarmLoc,
		avpAlarmSev,
		avpAlarmText}
	DESCRIPTION 
		"MPP logging attempt to system log failed"
 ::= 204


avpTRAPQSNMP02605 TRAP-TYPE
	ENTERPRISE avpNotification
	VARIABLES {
		avpAlarmTime,
		avpAlarmLoc,
		avpAlarmSev,
		avpAlarmText}
	DESCRIPTION 
		"Test Alarm Notification"
 ::= 205


avpTRAPGENINFO TRAP-TYPE
	ENTERPRISE avpNotification
	VARIABLES {
		avpAlarmTime,
		avpAlarmLoc,
		avpAlarmSev,
		avpAlarmText}
	DESCRIPTION
		"Voice Portal system generic Informational alarm"
 ::= 900


avpTRAPGENMINOR TRAP-TYPE
	ENTERPRISE avpNotification
	VARIABLES {
		avpAlarmTime,
		avpAlarmLoc,
		avpAlarmSev,
		avpAlarmText}
	DESCRIPTION
		"Voice Portal system generic Minor alarm"
 ::= 901


avpTRAPGENMAJOR TRAP-TYPE
	ENTERPRISE avpNotification
	VARIABLES {
		avpAlarmTime,
		avpAlarmLoc,
		avpAlarmSev,
		avpAlarmText}
	DESCRIPTION
		"Voice Portal system generic Major alarm"
 ::= 902


avpTRAPGENCRITICAL TRAP-TYPE
	ENTERPRISE avpNotification
	VARIABLES {
		avpAlarmTime,
		avpAlarmLoc,
		avpAlarmSev,
		avpAlarmText}
	DESCRIPTION
		"Voice Portal system generic Critical alarm"
 ::= 903


avpTRAPSTATGREEN TRAP-TYPE
	ENTERPRISE avpNotification
	VARIABLES {
		avpAlarmTime,
		avpAlarmLoc,
		avpAlarmSev,
		avpAlarmText}
	DESCRIPTION 
		"Voice Portal system status is normal - no alarms"
 ::= 980


avpTRAPSTATMINOR TRAP-TYPE
	ENTERPRISE avpNotification
	VARIABLES {
		avpAlarmTime,
		avpAlarmLoc,
		avpAlarmSev,
		avpAlarmText}
	DESCRIPTION 
		"Voice Portal system status has Minor alarms"
 ::= 981


avpTRAPSTATMAJOR TRAP-TYPE
	ENTERPRISE avpNotification
	VARIABLES {
		avpAlarmTime,
		avpAlarmLoc,
		avpAlarmSev,
		avpAlarmText}
	DESCRIPTION 
		"Voice Portal system status has Major alarms"
 ::= 982


avpTRAPSTATCRIT TRAP-TYPE
	ENTERPRISE avpNotification
	VARIABLES {
		avpAlarmTime,
		avpAlarmLoc,
		avpAlarmSev,
		avpAlarmText}
	DESCRIPTION 
		"Voice Portal system status has Critical alarms"
 ::= 983


--
-- Conformance information
--

avpConf OBJECT IDENTIFIER 	::= { avpVoicePortal 4 }

avpGroups OBJECT IDENTIFIER 	::= { avpConf 1 }

avpCompls OBJECT IDENTIFIER 	::= { avpConf 2 }


avpCPUUtilization TRAP-TYPE
	ENTERPRISE avpNotification
	VARIABLES {
		avpAlarmTime,
		avpAlarmLoc,
		avpAlarmSev,
		avpAlarmText}
	DESCRIPTION 
		"CPU Utilization"
 ::= 994


avpMemoryFault TRAP-TYPE
	ENTERPRISE avpNotification
	VARIABLES {
		avpAlarmTime,
		avpAlarmLoc,
		avpAlarmSev,
		avpAlarmText}
	DESCRIPTION 
		"Memory Fault"
 ::= 995


avpDiskWarning TRAP-TYPE
	ENTERPRISE avpNotification
	VARIABLES {
		avpAlarmTime,
		avpAlarmLoc,
		avpAlarmSev,
		avpAlarmText}
	DESCRIPTION 
		"Disk Warning"
 ::= 996


avpDiskFull TRAP-TYPE
	ENTERPRISE avpNotification
	VARIABLES {
		avpAlarmTime,
		avpAlarmLoc,
		avpAlarmSev,
		avpAlarmText}
	DESCRIPTION 
		"Disk Full"
 ::= 997

END
